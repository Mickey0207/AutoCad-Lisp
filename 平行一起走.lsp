(defun get-polyline-points (/ pts pt)
  (setq pts nil)
  (princ "\n依序點選主線各個彎折點，結束請按 Enter：")
  (while (setq pt m(getpoint "\n請點選一個點（Enter 結束）："))
    (setq pts (append pts (list pt)))
  )
  pts
)

(defun c:MPOLY (/ pts num basept refpt total-dist step i pline-ename offset-dist)
  (setq pts (get-polyline-points))
  (if (and pts (> (length pts) 1))
    (progn
      ;; 畫主線
      (command "_.PLINE")
      (foreach pt pts (command pt))
      (command "")
      (setq pline-ename (entlast))
      ;; 輸入平行線數量
      (setq num (getint "\n請輸入平行線數量: "))
      (if (and num (> num 1))
        (progn
          (setq basept (car pts))
          (setq refpt (getpoint basept "\n請點選正交方向的距離終點: "))
          (setq total-dist (distance basept refpt))
          (setq step (/ total-dist (float (num - 1))))
          (setq i 1) ; 從1開始，略過與主線重疊的那一條
          (while (< i num)
            (setq offset-dist (* i step))
            (command "_.OFFSET" offset-dist pline-ename refpt "")
            (setq i (1+ i))
          )
        )
        (princ "\n平行線數量必須大於1。")
      )
    )
    (princ "\n請至少點選兩個點。")
  )
  (princ)
)
(princ "\n請輸入 MPOLY 來畫多條正交分布的平行聚合線（支援彎折，效果最自然）。")
