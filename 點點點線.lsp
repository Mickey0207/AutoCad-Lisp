(defun c:OrthoPolys ( / ss i ent vcount pts newpts pt1 pt2 newpt)
  (prompt "\n請選取兩條或以上的聚合線：")
  (setq ss (ssget '((0 . "LWPOLYLINE"))))
  (if (and ss (> (sslength ss) 1))
    (progn
      (setq i 0)
      (while (< i (sslength ss))
        (setq ent (ssname ss i))
        (setq vcount (fix (vlax-curve-getEndParam ent)))
        ;; 取得所有頂點
        (setq pts '())
        (setq j 0)
        (while (<= j vcount)
          (setq pt (vlax-curve-getPointAtParam ent j))
          (setq pts (append pts (list pt)))
          (setq j (1+ j))
        )
        ;; 正交化頂點
        (setq newpts (list (car pts)))
        (setq k 1)
        (while (< k (length pts))
          (setq pt1 (nth (1- k) newpts))
          (setq pt2 (nth k pts))
          (if (> (abs (- (car pt2) (car pt1))) (abs (- (cadr pt2) (cadr pt1))))
            ;; X方向較長，Y值與前一點相同
            (setq newpt (list (car pt2) (cadr pt1) 0.0))
            ;; Y方向較長，X值與前一點相同
            (setq newpt (list (car pt1) (cadr pt2) 0.0))
          )
          (setq newpts (append newpts (list newpt)))
          (setq k (1+ k))
        )
        ;; 刪除原聚合線，建立新聚合線
        (entdel ent)
        (entmakex (append (list (cons 0 "LWPOLYLINE")
                                (cons 100 "AcDbEntity")
                                (cons 100 "AcDbPolyline")
                                (cons 90 (length newpts))
                                (cons 70 0))
                          (mapcar '(lambda (pt) (cons 10 pt)) newpts)))
        (setq i (1+ i))
      )
      (prompt "\n所有聚合線已正交化。")
    )
    (prompt "\n請至少選取兩條聚合線。")
  )
  (princ)
)
(princ "\n請輸入 OrthoPolys 來正交化多條聚合線。")
(princ)
